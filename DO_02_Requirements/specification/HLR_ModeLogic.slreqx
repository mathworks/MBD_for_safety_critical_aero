# HLR_ModeLogic

## 3: Modes of Operation (Functional)
The quadcopter shall have the following 8 modes of operation:
- Establish Communications
- Initialization
- Calibrate Sensors
- Ready for Flight
- Track Altitude
- Track Altitude and Position
- Lost Ball
- Land
- Crash
The requirements for each of the modes is described in the following sections.

## 16: Establish Communications (Container)

### 17: Enter Establish Communications at Power Up (Functional)
The Establish Communications mode shall be entered upon power up of the flight control system.

### 18: Enter Establish Communications from Crash (Functional)
The Establish Communications mode shall also be entered from the crash mode.

### 19: Enter Establish Communications from Land (Functional)
The Establish Communications mode shall also be entered from the Land mode when the quadcopter's roll angle is less than 5 deg, pitch angle is less than 5 deg, and vertical velocity less than 0.1 m/s.

## 21: Initialization (Container)

### 22: Enter Initialization from Establish Communications (Functional)
The Initialization mode shall be entered from the Establish Communications mode when WIFI communications with the ground station and Bluetooth LE communications with the payload processor are both established.

## 25: Calibrate the Sensors (Container)

### 26: Enter Calibrate Sensors from Initialization (Functional)
The Calibrate Sensors mode shall be entered from the Initialization mode when commanded by the ground station.

### 27: Enter Calibrate Sensors from Ready for Flight (Functional)
The Calibrate Sensors mode shall be entered from the Ready for Flight mode when commanded by the ground station.

## 29: Ready for Flight (Container)

### 30: Enter Ready for Flight from Calibration (Functional)
The Ready for Flight mode shall be entered from the Calibrate Sensors mode once the sensors have completed calibration and the ground station command for the mode is received.

## 33: Track Altitude (Container)

### 34: Enter Track Altitude from Ready for Flight (Functional)
The Track Altitude mode shall be entered from the Ready for Flight when a ball has been sensed to be in view of the camera.

### 35: Enter Track Altitude from Lost Ball (Functional)
The Track Altitude mode shall be entered from the Lost Ball mode when a ball has been sensed to be in view of the camera and the quadcopter is less than 10cm AGL.

## 37: Track Altitude and Position (Container)

### 38: The Track Altitude and Position mode shall be entered only from th... (Functional)
The Track Altitude and Position mode shall be entered from the Track Altitude mode when the quadcopter is at or above 10cm AGL.

### 39: The Track Altitude and Position mode shall be entered only from th... (Functional)
The Track Altitude and Position mode shall be entered from the Lost Ball mode when the ball has been sensed to be in view of the camera and the quadcopter is at or above 10cm AGL.

## 41: Lost Ball (Container)

### 42: Enter Lost Ball from Track Altitude (Functional)
The Lost Ball mode shall be entered from the Track Altitude mode when a ball that was sensed to be in the field of view of the camera is no longer sensed to be in the field of view of the camera.

### 43: Enter Lost Ball from Track Altitude and Position (Functional)
The Lost Ball mode shall be entered from the Track Altitude and Position mode when a ball that was sensed to be in the field of view of the camera is no longer sensed to be in the field of view of the camera.

## 46: Land (Container)

### 44: Enter Land from Lost Ball (Functional)
The Land mode shall be entered from the Lost Ball mode when the quadcopter has been in Lost Ball mode for 3 seconds.

### 47: Enter Land from Track Altitude (Functional)
The Land mode shall be entered from the Track Altitude mode when commanded by the ground station or if the battery voltage goes below 3.0 volts.

### 48: Enter Land from Track Altitude and Position (Functional)
The Land mode shall be entered from the Track Altitude and Position mode when commanded by the ground station or if the battery voltage goes below 3.0 volts.

## 50: Crash (Container)

### 51: Enter Crash (Functional)
The Crash mode shall be entered from any flight mode when commanded by the ground station or if the pitch or roll attitudes exceed 80 degrees while in any flight mode.

## #56: Justifications

### #57: Verified By Inspection
This Requirement is to be Verified by Inspection
